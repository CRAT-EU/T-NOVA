module rolemanager-impl-config {
   yang-version 1;
   namespace "urn:opendaylight:params:xml:ns:yang:rolemanager:impl:config";
   prefix "rolemanager-impl-config";


   import config { prefix config; revision-date 2013-04-05; }
   import opendaylight-md-sal-binding { prefix md-sal-binding; revision-date 2013-10-28;}

   description
       "Service definition for role manager project";
   revision "2014-12-10" {
       description
           "Initial revision";
   }

   identity rolemanager-impl-config {
       base config:module-type;
       config:java-name-prefix RolemanagerImpl;
   }

   augment "/config:modules/config:module/config:configuration" {
       case rolemanager-impl-config {
           when "/config:modules/config:module/config:type = 'rolemanager-impl-config'";
           container binding-aware-broker {
               uses config:service-ref {
                   refine type {
                       mandatory true;
                       config:required-identity md-sal-binding:binding-broker-osgi-registry;
                   }
               }
           }
       }
   }
}
